-- ===================================================================
-- AMP abstract syntax
-- ===================================================================
-- For now, I've reserved an OID in the Vlinder Software namespace (as
-- our second security protocol after SIT). This should move to an
-- IEEE namespace (1.3.111.2.1815.1.1), but the reservation will have
-- to stand.
AuthorizationManagementProtocol {
    iso(1) org(3) dod(6) internet(1) private(4) enterprise(1)
    vlinder-software(49974) security(0) protocols(0)
    authorization-management-protocol(1)
}

-- Definitions are organized into sections: The first section is the
-- one thing we expect (in this case, the AMP PDU)
-- Definitions within each section appear in alphabetical order
DEFINITIONS ::= BEGIN
    EXPORTS AMPPDU;
    
-- ===================================================================
-- the principal type
-- ===================================================================
    AMPPDU ::= SEQUENCE {
        -- the tbs is the SEQUENCE that is signed. The signature
	-- shall be over the full DER encoded SEQUENCE including
 	-- the tag and length of the tbs SEQUENCE
    	tbs SEQUENCE
         {
        version                             [0] IMPLICIT    Version,
	    -- uuid of this message, used to trace request-response and 
        -- challenge-response
        traceId                             [1] IMPLICIT    OCTET STRING (SIZE(16)),
        -- The priority of this message. Higher-priority messages take
        -- precedence over lower-priority ones. This allows intermediate
        -- devices to drop lower-priority messages in favor of higher-
        -- priority messages if their queues are full and more messages
        -- from the Authority arrive. 
        -- Priorities are listed below
        -- Messages coming up from devices do not have priorities associated
        -- with them, because they cannot safely be parsed by intermediate 
        -- devices (which do not have the originating device's public key to
        -- verify the message with).
        -- Note: we've tried to keep the number of priorities low to allow for
        --       an implementation with parallel queues (one per priority). We
        --       don't dictate the way it should be implemented (we allow a single
        --       priority queue), but using a small number of priorities allows
        --       either type of implementation
        priority                            [2] IMPLICIT    INTEGER(0..3) DEFAULT 0,
        address                             [3] IMPLICIT    Address,
        payload                             [4]             AMPPDUPayload
	}
        -- all messages are signed by the sender. 
	-- Messages sent from the Authority have their signatures verified 
  	-- Messages sent by Devices have their signatures verified at the first
   	-- hop and Authority only
        signature                           [5] IMPLICIT    Signature
    }
    
-- ===================================================================
-- types
-- ===================================================================
-- ===================================================================
-- structural types
-- ===================================================================
    AMPPDUPayload ::= CHOICE {
        encryptedPayload                    [0] AMPEncryptedPDUPayload,
        unencryptedPayload                  [1] UnencryptedAuthorityMessage,
        certificateChain                    [2] CertificateChain
    }

    AMPEncryptedPDUPayload ::= SEQUENCE {
        -- Payload is encrypted using an AES-GCM 256 AEAD, using no Additional 
        -- Data. The field contains the encrypted DER-encoded AMPPDUPayload,
        -- including the authentication tag from the AEAD.
        -- The key used to perform the AEAD is derived as follows:
        -- 1. using the peer's public key and the local private key, an ECDH (or 
        --    a DH) is performed. Note that this assumes that the peer identity 
        --    certificate contains a key suitable for doing this, so either a 
        --    static DH or ECDH key, or an ECDSA key that can also be used for 
        --    ECDH (the static ECDH key is preferred).
        -- 2. Using the shared secret derived in step 1, perform an HKDF using  
        --    the message's nonce. The output of the HKDF is the symmetric key 
	    --    used for the AEAD. This shall result in a 32-octet key.
        -- 3. The AES-GCM IV is set to 0.
        nonce                               [0] IMPLICIT    OCTET STRING (SIZE(32)),
        payload                             [1] IMPLICIT    OCTET STRING
    }

    -- the PDU payload: a top-level choice item
    AMPNonEncryptedPDUPayload ::= CHOICE {
        -- messages initiated by the Authority
        authorityMessage                    [0]     AuthorityMessage,
        -- messages initiated by a Device
        deviceMessage                       [1]     DeviceMessage,
        extendedMessage                     [2]     Extension
    }
    
    -- Note: for the priorities below, the basic reasoning is this:
    --       - priority 0 messages will be retried by the Authority if lost, so if they do
    --         get lost because of communications issues, that's not an issue
    --       - priority 1 messages affect communications to devices and the view the authority
    --         has on the system, but don't have a significant operational or security impact
    --         if lost
    --       - priority 2 messages would require the device to retry if lost, which could have
    --         an operational impact (e.g. an association not being permitted to be set up)
    --       - priority 3 messages have a security impact if lost
    -- Note: AMQP, when used as a transport between the Authority and the first-hop Master, 
    --       has its own priority field which, according to version 0.9.2 of the spec, can
    --       be either 0 or 1 (but is permitted to allow higher values). As we have assigned
    --       priority 3 to security-impacting messages, our priority 3 maps to AMQP priority 1
    --       an all other priorities map to AMQP priority 0. That is: in AMQP implementations
    --       to transport AMP, AMP priority 3 messages shall be sent with AMQP priority 1, all
    --       other messages shall be sent with AMQP priority 0.
    AuthorityMessage ::= CHOICE {
        associationAuthorizationStatus      [0]     IMPLICIT    
            AssociationAuthorizationStatus,
            -- Challenged if spontaneous, ACK if spontaneous
            -- priority 2
        routingTableRequest                 [1]     IMPLICIT
            RoutingTableRequest,
            -- priority 1
        routingTableStatusRequest           [2]     IMPLICIT
            RoutingTableStatusRequest,
            -- priority 1
        routingTableConfirmation            [3]     IMPLICIT
            RoutingTableConfirmation,
            -- priority 1
        routingTableUpdateConfirmation      [4]     IMPLICIT
            RoutingTableUpdateConfirmation,
            -- priority 1
        certificateResponse                 [5]
            CertificateResponse,
            -- priority 0
        challengeResponse                   [6]    IMPLICIT
            ChallengeResponse,
            -- priority 0
        policies                            [7]    IMPLICIT
            Policies,
            -- ACK, Challenged
            -- priority 0
        deviceCertificate                   [9]    IMPLICIT
            DeviceCertificate,
            -- ACK, Challenge
            -- priority 0
        certificateStatusResponse           [10]    IMPLICIT
            CertificateStatusResponse
            -- priority 0
    }

    -- These messages are unencrypted due to the need to initially send them 
    -- using multicast (which, because we use a point-to-point scheme for 
    -- encryption, we can't encrypt).
    UnencryptedAuthorityMessage ::= CHOICE {
        hello                               [0]     IMPLICIT
            Hello,
            -- priority 2
        certificateRevocations              [1]     IMPLICIT
            CertificateRevocations,
            -- ACK, priority 3
        authorityCertificate                [2]    IMPLICIT
            AuthorityCertificate,
            -- ACK, Challenge, priority 
            -- priority 0
        extendedMessage                     [3]     IMPLICIT
            Extension
    }
    
    -- Note: for the priorities below, the basic reasoning is this:
    --       - priority 0 messages will be retried by the device if lost, so if they do
    --         get lost because of communications issues, that's not an issue
    --       - priority 1 messages affect communications to devices and the view the authority
    --         has on the system, but don't have a significant operational or security impact
    --         if lost
    --       - priority 2 messages would require the device to retry if lost, which could have
    --         an operational impact (e.g. an association not being permitted to be set up)
    --       - priority 3 messages have a security impact if lost
    DeviceMessage ::= CHOICE {
        associationAuthorizationRequest     [0]     IMPLICIT
            AssociationAuthorizationRequest,
	    -- priority 2
        routingTable                        [1]     IMPLICIT
            RoutingTable,
	    -- priority 1
        routingTableRequest                 [2]     IMPLICIT
            RoutingTableRequest,
	    -- priority 1
        routingTableStatus                  [3]     IMPLICIT
            RoutingTableStatus,
	    -- priority 1
        routingTableStatusRequest           [4]     IMPLICIT
            RoutingTableStatusRequest,
	    -- priority 1
        routingTableUpdate                  [5]     IMPLICIT
            RoutingTableUpdate,
	    -- priority 1
        routingTableConfirmation            [6]     IMPLICIT
            RoutingTableConfirmation,
	    -- priority 0
        routingTableUpdateConfirmation      [7]     IMPLICIT
            RoutingTableUpdateConfirmation,
	    -- priority 0
        certificateRequest                  [8]
            CertificateRequest,
	    -- priority 2
        certificateResponse                 [9]
            CertificateResponse,
	    -- priority of the message being responded to
        challenge                           [10]    IMPLICIT
            Challenge,
	    -- priority of the message being challenged
        challengeResponse                   [11]    IMPLICIT
            ChallengeResponse,
	    -- priority of the challenge
        -- Per the 2021-05-21 discussions, the device doesn't need an acknowledgement 
        -- for non-zero-version-number policies, the device will repeat until it gets its
        -- policies overridden by the Authority. For anything else, the policies are
        -- already set by the Authority, so they're either OK, or the Authority will
        -- not have received an Ack for a recent change, in which case *it* will repeat.
        policies                            [12]    IMPLICIT
            Policies,
	    -- priority 0
        acknowlegement                      [13]    IMPLICIT
            Acknowledgement
	    -- priority of the message being acknowledged
    }
    
-- ===================================================================
-- service request types
-- ===================================================================
    -- Sent by the Device when it gets a new set of policies or a new
    -- authority certificate (AuthorityCertificateChange) from the Authority.
    -- Authority will re-send the change until it is blue in the face otherwise.
    -- Note: the acknowledgement of a challenged message acknowledges the
    -- original message, not the challenge response.
    Acknowledgement ::= Challenge

    AuthorityCertificate ::= CertificateChain

    -- Sent by a Device to an Authority to request authorization to
    -- communicate on a MOA.
    -- The Authority SHALL respond with an 
    -- AssociationAuthorizationStatus unless the device making the 
    -- request has been revoked or the signature on the message does
    -- not verify
    -- The Device shall initiate this request if its policies require
    -- it to do so.
    -- the associationAttributeHash is a hash of the attribute certificate 
    -- that describes the association, if available. Devices that have this
    -- information SHALL include the hash in the authorization request.
    AssociationAuthorizationRequest ::= SEQUENCE {
        associationName                     AssociationName,
        associationAttributeHash            Hash OPTIONAL
    }
    
    -- Sent by the Authority in response to an 
    -- AssociationAuthorizationRequest
    -- May also be sent by the Authority if it, for any reason, decides
    -- to revoke authorization for an association.
    -- If sent in response to an AssociationAuthorizationRequest that contained
    -- an associationAttributeHash for the current associationAttributes, the
    -- Authority MAY omit sending the associationAttributes to save
    -- bandwidth.
    AssociationAuthorizationStatus ::= SEQUENCE {
        associationName                     AssociationName,
        authorization                       AssociationAuthorization,
        associationAttributes               Certificate OPTIONAL
    }

    CertificateChain ::= SEQUENCE {
        caCertificates                      SEQUENCE OF Certificate,
        identityCertificate                 Certificate
    }
    
    CertificateRequest ::= CHOICE {
        attributeCertificateIssuer      [0] DistinguishedName,  -- for use to ask for a chain leading up to an Attribute Certificate
        identityCertificateSubject      [1] DistinguishedName   -- for use to ask for a chain leading up to an Identity Certificate
    }

    CertificateStatusRequest ::= SEQUENCE {
        issuerNameHash                      [0] Hash,               -- hash of the issuer's distinguished name as taken from the certificate
                                                                -- NOTE: This is a hash of the complete DER-encoded Distinguished Name 
                                                                --       as it appears in the encoded X.509 certificate. For 
                                                                --       interoperability, if possible, this should not be re-encoded.
                                                                --       The calculation of the hash should start at the first octet
                                                                --       of the SEQUENCE encoding of the Distinguished Name.
        -- NOTE: implicitly tagged (and keep it that way) so the parser can treat the integer as an octet string and keep it unbounded in size - for parsers that don't support integers of more than 64 bits
        certificateID                       [1] IMPLICIT INTEGER             -- serial number of the certificate taken from the certificate
    }
    
    CertificateStatusResponse ::= SEQUENCE {
        issuerNameHash                      [0] Hash,               -- hash of the issuer's distinguished name as taken from the certificate
        -- NOTE: implicitly tagged (and keep it that way) so the parser can treat the integer as an octet string and keep it unbounded in size - for parsers that don't support integers of more than 64 bits
        certificateID                       [1] IMPLICIT INTEGER,            -- serial number of the certificate taken from the certificate
        certificateStatus                   [2] CertificateStatus
    }
    
    -- Sent by an Authority or a device to convey a certificate, including the chain leading up to it, or its status if it's bad
    CertificateResponse ::= CHOICE {
        certificateChain                [0] CertificateChain,
        certificateStatus               [1] CertificateStatus
    }
    
    CertificateRevocations ::= SEQUENCE OF SEQUENCE {
        issuer                              DistinguishedName,   -- name of the CA we're relaying the revocation from
        thisUpdate                          UTCTime,             -- copied (and possible converted) from the thisUpdate field from the (intermediate) CA's CRL
        revokedCertificates                 SEQUENCE OF CertificateRevocation
    }

    Challenge ::= SEQUENCE {
        challengedMessageType               ChallengeableMessageType,
        challengedMessageHash               Hash
    }
    
    ChallengeResponse ::= Challenge

    DeviceCertificate ::= CertificateChain

    -- Extensions are used by the implementation to extend AMP.
    -- In order be permissible for use with AMP, the following must be true:
    -- - the type field contains a valid OID describing the format of the value
    -- - the syntax of the value shall be well-defined and registered with the User Group
    -- - no extension shall be used for any message with substantially similar semantics to a message defined in the main protocol
    -- - registering an extension implies the DNP-UG may adopt it into the main protocol (which means it cannot be used as an extension afterwards)
    Extension ::= SEQUENCE {
       type OBJECT IDENTIFIER,
       critical BOOLEAN,
       value OCTET STRING
    }

    -- Sent by the Authority when it comes on-line to indicate to devices
    -- that, if they have something to say/ask, now is the time to do it.
    Hello ::= NULL
    
    -- Maintained by devices and sent by the Authority, the policies
    -- determine the behavior of the device is various
    -- security-related circumstances, especially when the Authority is not
    -- available.
    -- Policies are sent by a device whenever the local policy version is 0.
	-- Only policies for which the local version is 0 are sent. Whether the
	-- contents of the policy is included in the report is configurable.
    -- Note that if policies are changed out-of-band, the
    -- version of the locally changed policies SHALL bet set to 0 and
	-- the device will start periodically sending those policies to the
	-- Authority until they are overriden by the Authority.
    -- The device SHALL be configurable for the interval for sending 
    -- the policies to the Authority when the version is 0. That interval
    -- SHALL NOT be infinite if the device has an Authority.
    Policies ::= SET OF Policy
    -- TODO: need time-outs for device verification periodicity, boolean to indicate
    --       whether to verify device when communications are established
	
    Policy ::= SEQUENCE {
        -- Non-negative integer version of the policies. If changed, must be
        -- strictly greater than any previous version of the policy
        -- sent by the Authority so it can be validated by the device.
        -- The device shall not accept a policy that is different from its
        -- current policy if its version number is smaller than or
        -- equal to that of its current policy but shall challenge such a 
        -- policy and apply it only if the challenge succeeds. Any successful
        -- change of policy commanded by the Autority shall be acknowledged.
        -- Built-in default configurations have version 0. The Authority 
        -- shall not use 0 as a policy version number.
        version                             INTEGER,
        type                                OBJECT IDENTIFIER,
        value                               ANY
    }
    
    -- Sent by devices in response to a RoutingTableRequest to convey
    -- the entire routing table.
    -- The routing table may exceed the size of an AMP PDU (which has
    -- to fit in an SPDU, which maybe as small as 254 bytes), so it
    -- may be sent in several "chunks" with the "moreFollows" bit set
    -- on each but the last PDU. The table version starts at 0 and is
    -- incremented every time an entry is visibly added to, modified
    -- in, or removed from, the device's table. Thus, other devices
    -- can verify whether the table has changed by reading the table
    -- version (conveyed in the RoutingTableStatus message). Changes
    -- to the table are considered “visible” if they are communicated
    -- to the peer device (i.e. the Master or the Authority). Internal
    -- changes to the routing table shall not be reflected in the
    -- communicated version.
    -- Entries in the table have no particular order.
    RoutingTable ::= SEQUENCE {
        -- TODO these integers should be bounded
        tableVersion                        INTEGER,
        sequenceNumber                      INTEGER,
        routingTable                        SET OF RoutingTableEntry,
        -- in case the routing table exceeds to maximum size of
        -- an AMP PDU
        moreFollows                         BOOLEAN DEFAULT FALSE
    }
    
    -- Sent by a device or an Authority to acknowledge receipt of
    -- part of the routing table, so the next message can be sent
    -- by the device.
    -- The AMPPDU's traceId shall match the traceId of the message
    -- being acknowledged. Other than that, this message has no
    -- payload.
    RoutingTableConfirmation ::= INTEGER
    
    -- Request to read the routing table. If the entire table is
    -- read (operation == read) the tableVersion field shall not
    -- be included in the message. If an update is requested, the 
    -- tableVersion shall be set to the last version obtained by
    -- the requesting device. In the former case, the response
    -- shall be a RoutingTable. In the latter case, it shall be:
    -- - if the version is still the same, a RoutingTableStatus
    --   message with the current version
    -- - if entries have been added but no entries have been removed,
    --   a RoutingTableUpdate message (or a series of
    --   RoutingTableUpdate messages) listing the entries that have
    --   been added
    -- - if entries have been removed but no entries have been added,
    --   a RoutingTableUpdate message (or a series of RoutingTableUpdate
    --   messages) listing the entries that have been removed
    -- - if entries have been removed and entries have been added,
    --   at least two RoutingTableUpdate messages, one listing the
    --   entries that have been removed and one listing the entries
    --   that have been added. Added and removed entries may be
    --   conveyed in any order. If there are more additions and/or
    --   removals than can fit in a single message there will be
    --   more than two messages in the response.
    RoutingTableRequest ::= SEQUENCE {
        operation                           RoutingTableRequestOperation,
        tableVersion                        INTEGER OPTIONAL
    }
    
    -- Sent by a device to indicate the current status (i.e. version)
    -- of the routing table
    -- Note that this version drops to 0 on device restart. The DNP3
    -- Application Layer receives a separate indication of device
    -- restart in an IIN, which should be forwarded to AMP. If 
    -- a remote device restarts, the local version of their routing
    -- table should be set to 0.
    -- A routing table with version number 0 shall always be empty.
    -- The newTable flag shall be set when the device has never reported
    -- on the status of this table to the requested before - e.g. after
    -- restart. Note that this requires the device to keep track of who
    -- it has communicated the status of the table to.
    RoutingTableStatus ::= SEQUENCE {
        tableVersion                        INTEGER,
        newTable                            BOOLEAN
    }
    
    -- Sent by a device or the Authority to request the current
    -- status (i.e. version) of the routing table. Has no payload.
    RoutingTableStatusRequest ::= NULL
    
    -- Update for the routing table. May be used (by a device) to
    -- indicate that entries have been added or removed from the
    -- routing table. A single message can only contain additions
    -- xor removals (not both). The tableVersion in the message
    -- shall indicate the current version of the table. The
    -- moreFollows field shall be present and set to true
    -- if any more messages are needed to convey the additions &
    -- removals from the table.
    -- If sent in response to a RoutingTableRequest and a device
    -- has both been added and removed from the table between the
    -- version in the request and the version in the response, both
    -- events shall be reported in order (such as to prevent the ABA
    -- problem).
    RoutingTableUpdate ::= SEQUENCE {
        sequenceNumber                      INTEGER,
        operation                           RoutingTableUpdateOperation,
        entries                             SET OF RoutingTableEntry,
        tableVersion                        INTEGER,
        moreFollows                         BOOLEAN DEFAULT FALSE
    }
    
    -- Sent by a device or an Authority to acknowledge receipt of
    -- part of a routing table update, so the next message can be sent
    -- by the device.
    -- The AMPPDU's traceId shall match the traceId of the message
    -- being acknowledged. Other than that, this message has no
    -- payload.
    RoutingTableUpdateConfirmation ::= INTEGER
    
-- ===================================================================
-- supporting types
-- ===================================================================
    Address ::= SEQUENCE {
        -- "to" address
        targetName                          [0] IMPLICIT DistinguishedName,
        -- "from" address
        sourceName                          [1] IMPLICIT DistinguishedName
    }

    -- NOTE: The distinguished names in this object shall contain the common 
    --       name (i.e. they are not relative distinguished names)
    AssociationName ::= SEQUENCE {
        masterDistinguishedName             DistinguishedName,
        outstationDistinguishedName         DistinguishedName
    }

    Certificate ::= OCTET STRING

    CertificateRevocation ::= SEQUENCE {
        userCertificate                     INTEGER,
        revocationDate                      UTCTime
    }
    
    -- CommonName from the certificate, must be system-wide unique
    -- NOTE: not used directly in the syntax elsewhere, but the requirement 
    --       for it to be part of every DistinguishedName and for it to be 
    --       system-wide unique remains.
    CommonName ::= UTF8String

    Fingerprint ::= Hash
    
    Hash ::= SEQUENCE {
        algorithm                           OBJECT IDENTIFIER,
        digest                              OCTET STRING
    }

    RoutingTableEntry ::= SEQUENCE {
        name DistinguishedName,
        
        flags BIT STRING
        {
            trusted (0),            -- certificate was verified - the device is authentic
            trustedSource (1),      -- certificate of the device that reported this entry to us (and every device in between) is verified
            master (2),             -- the device is configured as a master (not mutually exclusive with being an outstation)       
            outstation (3)          -- the device is configured as an outstation (not mutually exclusive with being a master)
        },

        -- hash of the device's public key (the algorithm should always be SHA256)
        fingerprint Fingerprint
    }
    
    Signature ::= SEQUENCE {
        algorithm                           OBJECT IDENTIFIER,
        signatureValue                      BIT STRING
    }

-- ===================================================================
-- Policy structures
-- ===================================================================
    -- Policy to determine whether a device is permitted to continue
    -- communicating when either its own Identity Certificate or that
    -- of the peer expires.
    -- The recommended default is to permit continued communications 
    -- until the Update Key also expires.
    PermitCommunicationsOnAuthenticationExpirationPolicy ::= SEQUENCE {
        mayCommunicate                      AuthenticationExpirationCommunicationPolicy
    }
    
    -- The certificates used by the device to authenticate the
    -- Authority, and thus instill trust in it, is set using this policy.
    AuthoritySignatureVerificationPolicy ::= SEQUENCE {
        -- Identity certificates for the Authority(ies)
        authorityIdentityCertificates       [1] IMPLICIT    SET OF Certificate OPTIONAL,
        -- Intermediate CA certificates for the Authority(ies)
        authorityCACertificates             [2] IMPLICIT    SET OF Certificate OPTIONAL,
        -- Identity certificate of the trusted root CA.
        rootOfTrustCertificate              [3] IMPLICIT    Certificate OPTIONAL
    }
    
    -- Once the authorization for an association is in place, it may need to be refreshed.
    -- Whether that is the case and, if so, at what interval, is specified in the 
    -- authorized association policy.
    AuthorizedAssociationPolicy ::= SEQUENCE {
        refreshAuthorization                [1] IMPLICIT    AuthorizationRefreshPolicy,
        refreshAuthorizationInterval        [2] IMPLICIT    INTEGER OPTIONAL,
        -- If authorization refresh requests are recurring,
        -- indicates the interval at which the device should ask,
        -- in seconds. Required if refreshAuthorization is not never(1)
        refreshTimeout                      [3] IMPLICIT    INTEGER OPTIONAL
   }

    -- Each Master-Outstation Association has a role, or a set of roles, assigned to it.
    -- These roles are defined in IEC 62351-8. If an association is authorized but does
    -- not have an Attribute Certificate that specifies the applicable roles, the Master 
    -- may assume a set of default roles according to the default access policy.
    DefaultAccessPolicy ::= SEQUENCE {
        defaultRoles                        IECUserRoles
    }

    DeviceAuthenticationPolicy ::= SEQUENCE {
        -- Indicates whether full PKI verification is required for device authentication.
        -- To be compliant to AMP, this is required to be true. However, to allow for
        -- scenarios where the Authority and the PKI it is part of to not (yet) be present,
        -- this may be false as a transitory case.
        requireCertificateChainValidation BOOLEAN,
        permitSelfSignedIdentityCertificates BOOLEAN
    }
    DeviceCertificateValidationPolicy ::= SEQUENCE {
        -- Indicates when a device should ask for authentication of
        -- the other device (i.e. validate that the certificate has 
        -- not been revoked)
        requestValidation               RequestValidationPolicy,    
        -- If authentication requests are recurring, indicates the
        -- interval at which the device should ask, in seconds.
        -- Required if requestValidation is recurring(5)
        requestValidationInterval       INTEGER OPTIONAL
    }
    
    UnauthorizedAssociationPolicy ::= SEQUENCE {
        allowCommunication BOOLEAN
    }

    RoutingPolicy ::= SEQUENCE {
        -- number of seconds between updates
        routingTableUpdatePeriod            INTEGER,
        -- Number of seconds the table should be deemed valid without updates being received
        -- (should typically be longer than the time between updates)
        routingTableTTL                INTEGER
    }

-- ===================================================================
-- enumerations
-- ===================================================================
	AssociationAuthorization ::= INTEGER {
        -- some status other than the following / unknown. Should not
        -- be used except as a place-holder. Shall not be sent over
        -- the wire.
        other(0),
        -- the association is authorized to exist
        authorized(1),
        -- the association is not authorized to exist, but also not
        -- explicitly denied. Whether devices are permitted to
        -- communicate is a local policy matter.
        unauthorized(2),    
        -- the association is not authorized. Devices shall not
        -- communicate
        denied(3)
    }
    
    AuthenticationExpirationCommunicationPolicy ::= INTEGER {
        -- Something other than the following/unknown. Should not be
        -- used except as a place-holder. Shall not be sent over the
        -- wire.
        other(0),
        -- Communication may continue after the Identity Certificate
        -- expires until the Update Key also expires
        while-update-key-valid(1),
        -- Communications case upon expiry of the Identity Certificate
        no-communication(2)
    }
    
    AuthorizationRefreshPolicy ::= INTEGER {
        other(0),
        recurring(1),
        never(2)
    }

    CertificateStatus ::= INTEGER {
        other(0),
        good(1),
        revoked(2),
        unknown(3)
    }

    ChallengeableMessageType ::= INTEGER {
        -- other(0) shall not be used for the message type. 
        other(0),
        -- These values are used to identify a message in a 
        -- Challenge or a ChallengeResponse
        device-revocation(1),
        association-authorization-status(2),
        device-certificate(5),
        device-status(8),
        policies(12),
        routing-table-update(16)
    }
    
    RequestValidationPolicy ::= INTEGER {
        other(0),
        at-discovery(1),
        at-association(2),
        at-session-initiation(3),
        recurring(4),
        never(5)
    }
    
    RevocationReason ::= INTEGER {
        -- The device was revoked for some reason other than one of the 
        -- enumerated ones. The reason shall be specified in the 
        -- reasonString field of the revocation message.
        other(0),
        -- The device was decommissioned and should not longer be part 
        -- of the system. Devices shall no longer communicate with it. 
        -- It may be re-instated later.
        device-decommissioned(1),
        -- The device was compromised and shall be removed from the 
        -- system. Devices shall no longer communicate with it.
        device-compromised(2),
        -- Reason for revocation is not specified.
        unspecified(3)
    }
    
    RoutingTableUpdateOperation ::= INTEGER {
        -- devices listed in the message are added to the table
        add(1),
        -- devices listed in the message are removed from the table
        remove(2),
        -- devices listed in the message have changed state
        -- (e.g. trust or trustedSource state changed)
        modify(3)
    }
    RoutingTableRequestOperation ::= INTEGER {
        -- request is to read the entire table
        read(1),    
        -- request is to obtain updates to the table since the
        -- given version
        update(2)
    }

-- ===================================================================
-- Object identifiers
-- ===================================================================
    authorization-management-protocol       OBJECT IDENTIFIER ::= {
        iso(1) org(3) dod(6) internet(1) private(4) enterprise(1)
        vlinder-software(49974) security(0) protocols(0)
        authorization-management-protocol(1)
    }

    event                                   OBJECT IDENTIFIER ::= { authorization-management-protocol 1 }
    controller-event                        OBJECT IDENTIFIER ::= { event 0 }
    master-event                            OBJECT IDENTIFIER ::= { event 1 }
    outstation-event                        OBJECT IDENTIFIER ::= { event 2 }
    authority-event                         OBJECT IDENTIFIER ::= { event 3 }
	
    policy                                                      OBJECT IDENTIFIER ::= { authorization-management-protocol 2 }
    permit-communications-on-authentication-expiration-policy   OBJECT IDENTIFIER ::= { policy 0 }
    authority-signature-verification-policy                     OBJECT IDENTIFIER ::= { policy 1 }
    authorized-association-policy                               OBJECT IDENTIFIER ::= { policy 2 }
    default-access-policy                                       OBJECT IDENTIFIER ::= { policy 3 }
    device-authentication-policy                                OBJECT IDENTIFIER ::= { policy 4 }
    device-certificate-validation-policy                        OBJECT IDENTIFIER ::= { policy 5 }
    unauthorized-association-policy                             OBJECT IDENTIFIER ::= { policy 6 }
    routing-policy                                              OBJECT IDENTIFIER ::= { policy 7 }

    entity                                  OBJECT IDENTIFIER ::= { authorization-management-protocol 3 }
    authority                               OBJECT IDENTIFIER ::= { entity 0 }
    device                                  OBJECT IDENTIFIER ::= { entity 1 }
	
-- ===================================================================
-- "borrowed" types
-- ===================================================================

-- ===================================================================
-- from RFC 5912
-- ===================================================================
    DistinguishedName ::= RDNSequence
    RDNSequence ::= SEQUENCE OF RelativeDistinguishedName
    RelativeDistinguishedName ::= SET OF SingleAttribute
    SingleAttribute ::= SEQUENCE {
        type OBJECT IDENTIFIER,
        value ANY -- depends on the type OID
    }

-- ===================================================================
-- from IEC 62351-8
-- ===================================================================
    IECUserRoles ::= SEQUENCE OF UserRoleInfo

    UserRoleInfo ::= SEQUENCE { -- contains the role information blob
        -- IEC62351 specific parameter
        userRole                        SEQUENCE SIZE (1..MAX) OF RoleID,
        aor                             UTF8String (SIZE(1..64)),
        revision                        INTEGER (0..255),
        roleDefinition                  UTF8String (0..23),
        -- optional fields to be used within IEEE 1815 and IEC60870-5, shall be absent in AMP
        operation                       Operation OPTIONAL,
        statusChangeSequenceNumber      INTEGER (0..4294967295) OPTIONAL,
    }

    RoleId ::= INTEGER (-32768..32767)

    -- not used
    Operation ::= ENUMERATED { add (1), delete (2), change (3) }

-- ===================================================================
-- syntax specification versions
-- ===================================================================
    
    -- unofficial versions are denoted with datecodes. This leaves
    -- official versions with over 20,000,000 possible versions
    -- before there is a possibility of collision, and clearly
    -- shows the difference between official and unofficial versions.
    Version ::= INTEGER { v20210730(20210730) }
END
